; =======================================
; CHECK_FILE.LSP
; кнопка (^C^C_CHECK_FILE) лого (RCDATA_16_3D_ARRAY)
; Проверка лишних слоев, блоков и типов линий
; =======================================
; Удачной работы!
; LarinPV, 2025г.

(defun c:CHECK_FILE (/ allowedLayers allowedBlocks allowedLTypes allLayers allBlocks allLTypes extraLayers extraBlocks extraLTypes layer0Count)
  
  ;; === ДОПУСТИМЫЕ СЛОИ ===
  (setq allowedLayers
    '("0" "Граница выполненных работ" "Заливка гидрографии" "Заливка автодорог" "Объекты производства" "Электроснабжение" "Связь" "Прочие коммуникации" "Теплоснабжение" "Ограждения и границы" "Растительность грунты болота" "Рельеф" "Гидрография и ГТС" "Дороги и мосты" "Строения здания" "Геопункты" "Рамка планшета" "Газоснабжение" "Канализация" "Водоснабжение"))

  ;; === ДОПУСТИМЫЕ БЛОКИ ===
  (setq allowedBlocks '("газ.столбик" "g5_095" "500_065" "500_063" "g5_174_2b" "107-1" "500_078" "500_Задвижка" "500_330" "500_074" "500_071" "500_069_2" "500_069_1" "500_137" "500_135_2" "500_135_1" "g5_476_3" "g5_475a" "g5_475_5c" "g5_475_5b" "g5_475_5a" "g5_475_5" "g5_474c_2" "g5_474c_1" "g5_474c" "g5_474b_2" "g5_474b_1" "g5_474b" "g5_474a_2" "g5_474a_1" "g5_474a" "g5_468" "g5_466" "g5_464" "g5_463b" "g5_463a" "g5_458" "g5_456" "g5_441" "g5_440_2" "g5_440_1" "g5_439_2" "g5_439_1" "g5_438_2" "g5_438_1" "g5_437_2" "g5_437_1" "g5_436" "g5_433" "g5_432_2" "g5_432_1" "g5_434" "g5_431_2" "g5_431_1" "g5_430" "g5_429_2" "g5_429_1" "g5_428" "g5_427" "g5_426" "g5_425" "g5_424" "g5_423_2" "g5_423_1" "g5_422_2" "g5_422_1" "g5_421" "g5_420_2" "g5_420_1" "g5_419" "g5_416" "g5_415" "g5_411" "g5_410" "g5_409" "g5_408" "g5_407" "g5_406" "g5_405e" "g5_405d" "g5_405c" "g5_405b" "g5_405a" "g5_404" "g5_403" "g5_402" "g5_401" "g5_400" "g5_399" "g5_396_2" "g5_396_1" "g5_395_2" "g5_395_1" "g5_394" "g5_391" "g5_390_8" "g5_390_7" "g5_390_6" "g5_390_5" "g5_390_4" "g5_390_3" "g5_390_2" "g5_390_1" "g5_388_3" "g5_388_2" "g5_388_1" "g5_384" "g5_383" "g5_382" "g5_381" "g5_380" "g5_379" "g5_371" "g5_370" "g5_369" "g5_368" "g5_367_3b" "g5_367_3a" "g5_367_2" "g5_367_1" "g5_210_6" "g5_210_5" "g5_348b" "g5_348a" "g5_346" "g5_343" "g5_342" "g5_339" "g5_338" "g5_337a" "g5_334a" "g5_329_6" "g5_327_2" "g5_327_1" "g5_326_2" "g5_326_1" "g5_325" "g5_323_3" "g5_312" "g5_311_2" "g5_311_1" "g5_307" "g5_306" "g5_305" "g5_304_4" "g5_304_3" "g5_304_2" "g5_243" "g5_238_1b" "g5_238_1a" "g5_231" "g5_230" "g5_229" "g5_228" "g5_227" "g5_224_4" "g5_224_3" "g5_224_2" "g5_222_2" "g5_222_1" "g5_213" "g5_149_2" "g5_149_1" "g5_148" "g5_147" "g5_145" "g5_142" "g5_140_2" "g5_140_1" "g5_139" "g5_128b" "g5_128a" "g5_116" "g5_115_2" "g5_115_1" "g5_114_4" "g5_113c" "g5_113b" "g5_113a" "g5_112" "g5_111_3d" "g5_111_3c" "g5_111_3b" "g5_111_3a" "g5_111_3" "g5_111_2" "g5_111_1d" "g5_111_1c" "g5_111_1b" "g5_111_1a" "g5_111_1" "g5_106_1a" "g5_105_2" "g5_099" "g5_096" "g5_093" "g5_092" "g5_091_2" "g5_091_1" "g5_089_2" "g5_089_1" "g5_082" "g5_080" "g5_079" "g5_078" "500_Заглушка" "500_067_2" "500_067_1" "500_066" "500_059_2" "500_058_2" "500_058_1" "500_057" "500_056" "500_052" "500_040" "500_038" "500_030" "500_029_3" "500_029_2" "500_025" "500_029_1" "500_012" "500_011_2" "500_010" "500_009" "500_008" "500_007" "500_006" "500_005_3" "500_005_2" "500_005_1" "500_003" "500_001" "g5_304_1" "g5_301" "g5_299" "g5_298" "g5_297" "g5_296" "g5_295" "g5_294" "g5_292c" "g5_292b" "g5_292a" "g5_291" "g5_290" "g5_289_2" "g5_289_1" "g5_288" "g5_285" "g5_284c" "g5_284b" "g5_284a" "g5_282" "g5_281_2" "g5_281_1" "g5_280_2" "g5_280_1" "g5_266" "g5_209" "g5_207_2c" "g5_207_2a" "g5_207_2b" "g5_207_1" "g5_206_5" "g5_206_3" "g5_206_2" "g5_206_1" "g5_204b" "g5_204a" "g5_184" "g5_183" "g5_182" "g5_181" "g5_179b" "g5_179a" "g5_178" "g5_174_3b" "g5_174_3a" "g5_174_1" "g5_172_1" "g5_171_2" "g5_171_1" "g5_122_7" "g5_122_3" "g5_121_7c" "g5_121_6f" "g5_121_6e" "g5_121_6d" "g5_121_6c" "g5_121_6b" "g5_121_6a" "g5_121_2c" "g5_121_2b" "g5_121_2a" "g5_120_3" "g5_119_2c" "g5_119_2b" "g5_119_2a" "g5_117svet_2" "g5_117svet_1" "g5_118" "g5_117z" "g5_117vx" "g5_117v" "g5_117t" "g5_117sv" "g5_117n" "g5_117m" "g5_117kl" "g5_117kb" "g5_117g" "g5_117el" "g5_117d" "g5_117b" "g5_117" "g5_110_2h" "g5_110_2g" "g5_110_2f" "g5_110_2e" "g5_110_2d" "g5_110_2c" "g5_110_2b" "g5_110_2a" "g5_110_2" "g5_110_1h" "g5_110_1g" "g5_110_1f" "g5_110_1e" "g5_110_1d" "g5_110_1c" "g5_110_1b" "g5_110_1a" "g5_110_1" "g5_109d" "g5_109c" "g5_109b" "g5_109a" "g5_109" "g5_108c" "g5_108b" "g5_108a" "g5_108" "g5_107_2b" "g5_107_2a" "g5_107_1c" "g5_107_1b" "g5_107_1a" "g5_106_2" "g5_106_1c" "g5_106_1b" "g5_011_7" "_NONE"))

  ;; === ДОПУСТИМЫЕ ТИПЫ ЛИНИЙ ===
  (setq allowedLTypes '("500_Линия" "500_5x2" "500_242" "500_254_2" "500_254_1" "500_8x1" "500_84b" "500_7x1" "500_5x1" "500_4x1" "500_486" "500_484" "500_483" "500_482" "500_481" "500_480" "500_479" "500_478" "500_477" "500_476_3" "500_476_2c" "500_476_2b" "500_476_2a" "500_476_1" "500_475_4b" "500_475_4a" "500_475_3" "500_475_2" "500_475_1" "500_474_4b" "500_474_4a" "500_474_3b" "500_474_3a" "500_474_2c" "500_474_2b" "500_474_2a" "500_474_1c" "500_474_1b" "500_474_1a" "500_473" "500_472" "500_3x1" "500_397_1" "500_386_4" "500_386_3" "500_386_2" "500_386_1" "500_366" "500_2x1" "500_278_7" "500_278_6b" "500_278_6a" "500_278_5" "500_274" "500_270" "500_218_2" "500_218_1" "500_2.5x1.5" "500_1x1" "500_1x0.5" "500_199" "500_193_3" "500_187" "500_164_2" "500_164_1" "500_163" "500_161_2" "500_161_1" "500_160b_2" "500_160b_1" "500_160a_2" "500_160a_1" "500_159_2" "500_159_1" "500_158_2" "500_158_1" "500_155" "500_10x2" "500_1.5x1.5" "500_1.5x1" "500_120_3b" "500_120_3a" "500_85b" "500_85a" "500_84a" "500_351" "500_347" "500_333" "500_332" "500_281_2" "500_281_1" "500_280_2" "500_280_1" "500_277_4" "500_276_2" "500_255" "500_146" "500_133" "500_132_2" "500_131_2" "500_119_3" "500_119_1" "KOMMUNIKACII" "1x1" "Continuous" "ByLayer" "ByBlock"))

  ;; === СОБРАТЬ ВСЕ СЛОИ В ЧЕРТЕЖЕ ===
  (setq allLayers '())
  (vlax-for lay (vla-get-Layers (vla-get-ActiveDocument (vlax-get-Acad-Object)))
    (setq allLayers (cons (vla-get-Name lay) allLayers))
  )

  ;; === СОБРАТЬ ВСЕ БЛОКИ ===
  (setq allBlocks '())
  (vlax-for blk (vla-get-Blocks (vla-get-ActiveDocument (vlax-get-Acad-Object)))
    (setq allBlocks (cons (vla-get-Name blk) allBlocks))
  )

  ;; === СОБРАТЬ ВСЕ ТИПЫ ЛИНИЙ ===
  (setq allLTypes '())
  (vlax-for ltype (vla-get-Linetypes (vla-get-ActiveDocument (vlax-get-Acad-Object)))
    (setq allLTypes (cons (vla-get-Name ltype) allLTypes))
  )

  ;; === ВЫЧИСЛЕНИЕ ЛИШНИХ / ПРОПАВШИХ ===
  (setq extraLayers (vl-remove-if '(lambda (x) (member x allowedLayers)) allLayers))
  (setq missingLayers (vl-remove-if '(lambda (x) (member x allLayers)) allowedLayers))
  (setq extraBlocks (vl-remove-if '(lambda (x) (member x allowedBlocks)) allBlocks))
  (setq extraBlocks (vl-remove-if '(lambda (x) (member x '("*Paper_Space0" "*Paper_Space" "*Model_Space"))) extraBlocks))
  (setq extraLTypes (vl-remove-if '(lambda (x) (member x allowedLTypes)) allLTypes))

  ;; === ЭЛЕМЕНТЫ НА СЛОЕ "0" ===
  (setq layer0Count 0)
  (vlax-for ent (vla-get-ModelSpace (vla-get-ActiveDocument (vlax-get-Acad-Object)))
    (if (and (= "0" (vla-get-Layer ent))
             (not (eq "AcDbBlockReference" (vla-get-ObjectName ent))))
      (setq layer0Count (1+ layer0Count))
    )
  )

  ;; === ФЛАГ ПРОБЛЕМ ===
  (setq hasProblems (or extraLayers missingLayers extraBlocks extraLTypes (> layer0Count 0)))

  ;; === ВЫВОД ===
  (if hasProblems
    (progn
      (princ "\n======================================")
      (princ "\nПРОБЛЕМАХ В ФАЙЛЕ:")

      (if extraLayers
        (princ (strcat "\nЛишние слои: " (apply 'strcat (mapcar '(lambda (x) (strcat x " ")) extraLayers)))))

      (if missingLayers
        (princ (strcat "\nОтсутствуют обязательные слои: " (apply 'strcat (mapcar '(lambda (x) (strcat x " ")) missingLayers)))))

      (if extraBlocks
        (princ (strcat "\nЛишние блоки: " (apply 'strcat (mapcar '(lambda (x) (strcat x " ")) extraBlocks)))))

      (if extraLTypes
        (princ (strcat "\nЛишние стили линий: " (apply 'strcat (mapcar '(lambda (x) (strcat x " ")) extraLTypes)))))

      (if (> layer0Count 0)
        (princ (strcat "\nСлой \"0\": есть элементы (" (itoa layer0Count) ")")))

      (princ "\n--------------------------------------")
      (princ "\nX Есть моменты, требующие внимания.")
    )
    (progn
      (princ "\n======================================")
      (princ "\nV Всё хорошо, лишних элементов нет.")
    )
  )

  (princ)
)

(princ "\nКоманда CHECK_FILE загружена. Введите CHECK_FILE для запуска.\n")
(princ)
